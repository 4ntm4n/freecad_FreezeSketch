# -*- coding: utf-8 -*-
# FreezeSketch.FCMacro
# A macro to convert a sketch into a ShapeBinder in FreeCAD's PartDesign workbench
#
# __Name__ = "Freeze Sketch"
# __Comment__ = "Converts a selected sketch into a ShapeBinder within a PartDesign Body, with options to delete the original sketch."
# __Author__ = "Anton Askling"
# __Version__ = "1.0"
# __Date__ = "2025-03-24"
# __License__ = "MIT"
# __Web__ = "https://github.com/4ntm4n/FreeCAD-FreezeSketch"
# __Icon__ = ":/icons/DrawStyleShaded.svg"
# __Help__ = "Select a sketch in a PartDesign Body and run the macro."
# __Status__ = "Stable"
# __Requires__ = "FreeCAD 0.19 or later"
# __Communication__ = "Report issues at https://github.com/4ntm4n/FreeCAD-FreezeSketch/issues"
# __Files__ = "FreezeSketch.FCMacro, manual_install/FreezeSketch.py, README.md"


import FreeCAD
import FreeCADGui
import PartDesign
from PySide import QtGui

# Function to get/set the user's preference for deleting the sketch
def get_delete_preference():
    # Check if a preference exists in FreeCAD's user parameters
    param = FreeCAD.ParamGet("User parameter:BaseApp/Preferences/Macro")
    return param.GetString("DeleteSketchPreference", "Ask")  # Default to "Ask" if not set

def set_delete_preference(value):
    param = FreeCAD.ParamGet("User parameter:BaseApp/Preferences/Macro")
    param.SetString("DeleteSketchPreference", value)

# Get the active document
doc = FreeCAD.ActiveDocument

# Get the selected objects
sel = FreeCADGui.Selection.getSelection()
if not sel:
    FreeCAD.Console.PrintError("Please select a sketch to freeze.\n")
    raise Exception("No sketch selected")

# Process the selected sketch
obj = sel[0]  # Take the first selected object
if obj.TypeId != "Sketcher::SketchObject":
    FreeCAD.Console.PrintError(f"Selected object '{obj.Label}' is not a sketch.\n")
    raise Exception("Selected object is not a sketch")

# Find the parent body (if any)
parent_body = None
for parent in obj.InList:
    if parent.TypeId == "PartDesign::Body":
        parent_body = parent
        break

if not parent_body:
    FreeCAD.Console.PrintError("The sketch must be inside a body.\n")
    raise Exception("No parent body found")

# Create a Shape Binder from the sketch
shape_binder = parent_body.newObject("PartDesign::ShapeBinder", obj.Label + "_ShapeBinder")
shape_binder.Support = obj
shape_binder.Label = obj.Label + "_ShapeBinder"

# Recompute the document
doc.recompute()

# Check the user's preference for deleting the sketch
delete_preference = get_delete_preference()
delete_sketch = False

if delete_preference == "Always":
    delete_sketch = True
elif delete_preference == "Never":
    delete_sketch = False
else:
    # Create a dialog box to ask the user if they want to delete the sketch
    dialog = QtGui.QMessageBox()
    dialog.setWindowTitle("Delete Original Sketch")
    dialog.setText(f"Do you want to delete the original sketch '{obj.Label}'?\nThe Shape Binder has been created and can be used independently.")
    dialog.setStandardButtons(QtGui.QMessageBox.NoButton)  # Remove default buttons

    # Add custom buttons
    always_button = dialog.addButton("Always", QtGui.QMessageBox.AcceptRole)
    yes_button = dialog.addButton("Yes", QtGui.QMessageBox.YesRole)
    no_button = dialog.addButton("No", QtGui.QMessageBox.NoRole)
    never_button = dialog.addButton("Never", QtGui.QMessageBox.RejectRole)

    dialog.exec_()

    # Determine the user's choice
    clicked_button = dialog.clickedButton()
    if clicked_button == always_button:
        delete_sketch = True
        set_delete_preference("Always")
    elif clicked_button == yes_button:
        delete_sketch = True
    elif clicked_button == no_button:
        delete_sketch = False
    elif clicked_button == never_button:
        delete_sketch = False
        set_delete_preference("Never")

# Delete the sketch if the user chose to
if delete_sketch:
    doc.removeObject(obj.Name)
    FreeCAD.Console.PrintMessage(f"Original sketch '{obj.Label}' has been deleted.\n")
else:
    FreeCAD.Console.PrintMessage(f"Original sketch '{obj.Label}' has been retained.\n")

FreeCAD.Console.PrintMessage(f"Shape Binder created for '{obj.Label}' as '{shape_binder.Label}'.\n")
